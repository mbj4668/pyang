module b {
  namespace "urn:b";
  prefix b;

  identity b;
  identity b2;

  container b {
    leaf q {
      type string;
    }
    leaf q3 {
      type string;
    }
  }
  container c {
    leaf q {
      type string;
    }
  }

}
