module a {
    namespace "urn:a";
    prefix a;

    import d { // warning: not used
        prefix d;
    }

    typedef xx { type string { length "1..10";} }
    typedef xx { type string { length "1..101";} } // error: already defined

    typedef ab { type ba; } // error: recursive typedef
    typedef ba { type ab; }
    typedef bb { type bb; } // error: recursive typedef

    typedef u1 {
        type union {
            type u2; // error: recursive typedef
            type string;
        }
    }
    typedef u2 {
        type union {
            type u1; // error: recursive typedef
            type int32;
        }
    }

    typedef a {
        type int32 {
            range "1 | 2..4 | 10";
        }
    }
    
    typedef ax {
        type int32 {
            length "1|2";  // error: length is bad restriction
        }
    }
    
    typedef b {
        type a {
            range "1 | 3..4 | 10";
        }
      default "3";
    }
    
    typedef b2 {
        type b {
            range "1 | 4"; // error; range does not match default
        }
    }
    
    typedef s1 {
        type string {
            pattern "a.*";
            pattern ".*b";
        }
        default "ac"; // error: default does not match second pattern
    }
        
    typedef ee {
        type enumeration {
            enum foo;
            enum bar {
                value 0; // error: 0 auto-assigned to foo
            }
            enum " bad"; // error: bad enum string
            enum "bad "; // error: bad enum string
            enum ""; // error: bad enum string
            enum "foo"; // error: already defined
            enum "100 years";
        }
    }

    typedef ff {
        type bits {
            bit foo {
                position 2;
            }
            bit bar;
            bit bax {
                position 3; // error: 3 auto-assigned to bar
            }
        }
    }

    typedef uu {
        type union {
            type uint8;
            type string {
                pattern "a*";
            }
        }
        default aa;
    }

    typedef foo {
        type union {
            type bempty; // error: bempty is 'empty', not allowed in union
            type int32;
        }
    }

    typedef bempty {
        type union {
            type string;
            type bempty2; // error: bempty2 is 'empty', not allowed in union
        }
    }

    typedef bempty2 {
        type empty;
    }

    container f {
        typedef cc { type int32; }
        leaf foo {
            type a:cc;
        }
        leaf bar {
            type leafref {
//                path "../h/b[x:foo = current()/../a]";
                path "../h/b[a:foo = current()/../a]";
            }
        }
        leaf bax {
            type leafref {
                path "../h[a = current()/../../f]/a";
            }
        }
        list h {
            key a;
            leaf a {
                type int32;
            }
        }
    }
    leaf f {
        type int32;
    }

    grouping foox { // error: circular grouping definition
    uses a:bar;
  }
  grouping bar {
    uses foox;
  }

  typedef u64ErrorEnum{
    type enumeration {
      enum overload {value 18446744073709551613;} // error - too big
      enum na;
      enum unknown;
    }
  }

  typedef xErrorEnum{
    type enumeration {
      enum overload {value 2147483646;}
      enum na;
      enum unknown; // error -- too big auto value
    }
  }

  typedef myuint64 {
    type uint64;
    default 123456789123456789;
  }
  
  container some-config {
    leaf myuint64leaf {
      type myuint64 {
        range "1..50000000";
      }
    }
  }

}
