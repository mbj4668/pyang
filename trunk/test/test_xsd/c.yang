module c {
  namespace "urn:c";
  prefix c;

  container x {
    description "hej";
    list y {
      key id;
      leaf id {
        type string;
      }
      leaf foo {
        type string;
      }
    }
    list z {
      key id;
      leaf id {
        type string;
      }
      leaf foo {
        type string;
      }
    }
    container u {
      list v {
        key id;
        leaf id {
          type string;
        }
        leaf foo {
          type string;
        }
      }
    }
  }
}
