module cmod {
  namespace "http://example.com/c";
  prefix c;

  import ietf-yang-metadata {
    prefix md;
  }

  import amod {
    prefix a;
  }
  
  identity "base-id";

  identity "derived-id" {
    base "base-id";
  }
  
  md:annotation "idann" {
    type identityref {
      base "base-id";
    }
  }

  md:annotation "iiann" {
    type instance-identifier;
  }

  md:annotation "strann" {
    if-feature a:abc;
  }

  md:annotation "u64ann" {
    type uint64;
  }
}
