module e {
  prefix e;
  namespace "urn:e";
  import ietf-interfaces {
    prefix if;
  }
  typedef foo {
    type string;
  }
  container x {
    container y;
    container bar {
      leaf z {
        type string;
      }
    }
  }
  typedef bar {
    type int32;
  }
}
