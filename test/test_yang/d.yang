module d {
  prefix d;
  namespace "urn:d";
  typedef foo {
    type string;
  }
  container x {
    container y;
    container bar {
      leaf z {
        type string;
      }
    }
  }
  typedef bar {
    type int32;
  }
}
