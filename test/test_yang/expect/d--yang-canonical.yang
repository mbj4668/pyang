module d {
  namespace "urn:d";
  prefix d;

  typedef foo {
    type string;
  }

  typedef bar {
    type int32;
  }

  container x {
    container y;
    container bar {
      leaf z {
        type string;
      }
    }
  }
}
