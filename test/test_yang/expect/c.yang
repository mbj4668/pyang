module a {
  namespace "urn:a";
  prefix a;

  typedef foo {
    type string;
  }

  typedef bar {
    type int32;
  }

  container x {
    container y;
    container bar {
      leaf z {
        type string;
      }
    }
  }
}
