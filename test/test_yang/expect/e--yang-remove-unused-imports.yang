module e {
  prefix e;
  namespace "urn:e";

  typedef foo {
    type string;
  }

  container x {
    container y;
    container bar {
      leaf z {
        type string;
      }
    }
  }

  typedef bar {
    type int32;
  }
}
