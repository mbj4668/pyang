module i {
  namespace "urn:i";
  prefix i;

  /* comment with empty line

     after empty line
   */

  container x {
    /* another comment

       with empty line
     */
    leaf y {
      type string;
    }
  }
}
