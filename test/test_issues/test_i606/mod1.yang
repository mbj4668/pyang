module mod1 {
  yang-version 1.1;
  namespace "urn:mod1";
  prefix m1;

  list lst {
    key "name le1 le2";
    status current;

    leaf name {
      type string;
      status obsolete; // error: illegal, since name is obsolete
    }

    leaf le1 {
      type string;
      status deprecated; // error: illegal, since name is deprecated
    }

    leaf le2 {
      type string;
      status current; // no errors
    }
  }
}
