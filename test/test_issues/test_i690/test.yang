module test {

  yang-version "1";

  namespace "http://test";

  prefix test;

  import test2 {
    prefix test2;
  }


  organization "x";
  contact "x";
  description "x";

  revision 2017-04-21 {
    description "1st revision.";
  }

  grouping testgrouping1 {
   leaf test {
    type string;
   }
  }
  grouping testgrouping {
    uses testgrouping1;
  }

  uses test2:testgrouping;
}
