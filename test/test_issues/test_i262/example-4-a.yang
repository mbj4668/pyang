module example-4-a {

  yang-version "1.1";

  namespace "http://example.com/example-4-a";

  prefix "ex4a";

  container bag {
    leaf foo {
      type uint8;
      default "0";
    }
    choice opts {
      default "a";
      case a {
        leaf bar {
          type boolean;
          default "true";
        }
      }
    }
  }
}
