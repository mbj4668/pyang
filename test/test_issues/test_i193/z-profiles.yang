submodule z-profiles {
  yang-version 1.1;
  belongs-to z-base {
    prefix z-b;
  }
  augment "/z-b:configs/z-b:profiles" {
    list profile {
      key name;
      leaf name {
        type leafref {
          path "../../foo";
        }
      }
    }
  }
}
