module mod1 {
  yang-version 1.1;
  namespace "urn:mod1";
  prefix m1;

  anydata reset {
    input {
      leaf start {
        type string;
      }
    }
    output {
      leaf finish {
        type string;
      }
    }
  }
}
