module test {

  namespace "http://example.com/test";

  prefix "t";

  import main {
    prefix "m";
  }

  include subtest;

  augment "/m:top" {
    container cnt {
      presence "yes";
    }
  }
}
