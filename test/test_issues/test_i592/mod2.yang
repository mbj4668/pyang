module mod2 {
  yang-version 1.1;
  namespace "urn:mod2";
  prefix m2;

  typedef base {
    type int8 {
      range "min..10 | 20..max";
    }
    //default "15";
  }

  typedef my1 {
    type base {
      range "min..11"; // error: '11' is bad value
    }
  }

  typedef my2 {
    type base {
      range "min..max"; // error: 'min' and 'max' are not in the same interval
    }
  }

  typedef my3 {
    type base {
      range "19..29"; // error: '19' is bad value
    }
  }

  typedef my4 {
    type base {
      range "15"; // error: '15' is bad value
    }
  }

  typedef my5 {
    type base {
      range "min"; // no errors
    }
  }

  typedef my6 {
    type base {
      range "max"; // no errors
    }
  }

  typedef my7 {
    type base {
      range "10..max"; // error: '10' is bad value
    }
  }

  typedef my8 {
    type base {
      range "255"; // error: '255' is bad value
    }
  }
}
