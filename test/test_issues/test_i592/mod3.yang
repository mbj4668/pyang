module mod3 {
  yang-version 1.1;
  namespace "urn:mod3";
  prefix m3;

  typedef base {
    type decimal64 {
      fraction-digits 2;
      range "1 .. 3.14 | 10 | 20 .. max";
    }
    //default "15";
  }

  typedef my1 {
    type base {
      range "min..11"; // error: '11' is bad value
    }
  }

  typedef my2 {
    type base {
      range "min..max"; // error: 'min' and 'max' are not in the same interval
    }
  }

  typedef my3 {
    type base {
      range "0.9 .. 2.12"; // error: '0.9' is bad value
    }
  }

  typedef my4 {
    type base {
      range "5.55"; // error: '5.55' is bad value
    }
  }

  typedef my5 {
    type base {
      range "min"; // no errors
    }
  }

  typedef my6 {
    type base {
      range "max"; // no errors
    }
  }

  typedef my7 {
    type base {
      range "19.9 .. max"; // error: '19.9' is bad value
    }
  }
}
