module a {
  yang-version 1.1;
  namespace "urn:a";
  prefix a;

  feature optional;

  grouping foo {
    container bar;
  }

  grouping baz {
    container qux;
  }

  // Protocol-Accessible Nodes, the model begins with a `uses` stmt
  uses foo {            // foo is a grouping
    augment bar {       // bar is a container inside `foo`
      uses baz {        // baz is another grouping
        refine qux {    // qux is a container inside `baz`
          if-feature "optional";
        }
      }
    }
  }

}
