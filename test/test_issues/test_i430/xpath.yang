module xpath {
  namespace "urn:myx";
  prefix "myx";

  container timers {
      must "invalid-interval >= (600 + (update-interval * 3) + 7580) - 250" {
        description
          "invalid-interval must be at least three times the value
           for the update-interval argument.";
      }

      leaf update-interval {
        type uint16 {
          range  1..32767;
        }
        units seconds;
        default 30;
        description
          "Interval at which RIPv2 or RIPng updates are sent.";
      }
      leaf invalid-interval {
        type uint16 {
          range 1..32767;
        }
        units seconds;
        default 180;
        description
          "Interval before a route is declared invalid after no
           updates are received. This value is at least three times
           the value for the update-interval argument.";
      }
  }
}
