module mod1 {
  yang-version 1.1;
  namespace "urn:mod1";
  prefix m1;

  container interfaces {
    list ifEntry {
      key "ifIndex";
      leaf ifIndex {
        type uint32;
      }

      leaf ifDescr {
        type string;
      }

      action reset {
        input {
          leaf start {
            type string;
          }
        }
        output {
          leaf finish {
            type string;
          }
        }
      }
    }
  }

  augment "/interfaces/ifEntry/reset" { // target node cannot be action
    leaf result {
      type string;
    }
  }
}
