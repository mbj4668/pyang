module main {
  yang-version 1.1;
  namespace "urn:main";
  prefix main;

  import base {
    prefix base;
  }

  import ext {
    prefix ext;
  }

  augment "/base:c/ext:b" {
    container a {
    }
  }
}
