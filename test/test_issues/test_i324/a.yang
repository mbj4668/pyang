module a {
  namespace "urn:a";
  prefix a;

  container a {
    leaf b {
      type union {
        type uint32 {
          range "1..2000000000";
        }
        type enumeration {
          enum "max"                          { value -1; }
        }
      }
      default "max";
    }
  }
}
