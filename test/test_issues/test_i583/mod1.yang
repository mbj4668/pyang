module mod1 {
  yang-version 1.1;
  namespace "urn:mod1";
  prefix m1;

  feature f1;
  feature f2;

  leaf le1 {
    type enumeration {
      enum aa {
        if-feature "f1";
      }

      enum bb;
      enum cc;
    }
    default "aa";
  }

 leaf le2 {
    type bits {
      bit aaa {
        position 0;
        if-feature "f1 and f2";
      }

      bit bbb;
      bit ccc;
    }
    default "aaa";
  }

  leaf le3 {
    type bits {
      bit aaa {
        position 0;
        if-feature "f2";
      }

      bit bbb;
      bit ccc {
        if-feature "f1";
      }
    }
    default "bbb ccc";
  }

}
