submodule y-profiles {
  yang-version 1;
  belongs-to y-base {
    prefix y-b;
  }

  include y-base2;

  // augments a node in the main module

  augment "/y-b:x-setting/y-b:configs/y-b:profiles" {
    list profile {
      key "name";
      leaf name {
        type string;
      }
    }
  }
}
