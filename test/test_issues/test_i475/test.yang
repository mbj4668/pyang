module test {
  yang-version 1.1;

  namespace urn:test;

  prefix test;

  container root {
    list child {
      key name;
      min-elements 3;
      max-elements 10;

      leaf name {
        type string;
      }

      leaf foo {
        mandatory true;
        config true;
        units 'dollar';
        type string;
      }
    }
  }
}
