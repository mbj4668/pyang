module test-dev {
  yang-version 1.1;
  namespace urn:test-dev;
  prefix test-dev;

  import test {
    prefix t;
  }

  deviation /t:root/t:child {
    deviate delete {
      max-elements 10;
      min-elements 3;
    }
  }

  deviation /t:root/t:child/t:foo {
    deviate delete {
      mandatory true;
      config true;
      units 'dollar';
    }
  }
}
