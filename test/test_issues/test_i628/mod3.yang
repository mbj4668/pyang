module mod3 {
  yang-version 1.1;
  namespace "urn:mod3";
  prefix m3;

  container interfaces {
    list ifEntry {
      key "ifIndex";
      leaf ifIndex {
        type uint32;
      }

      choice nodechoice {
        case nodecase {
          leaf name {
            type string;
          }
        }
      }
    }
  }

  augment "/interfaces/ifEntry/nodechoice" {//target node is choice, it is not a container or list node.
    leaf result {
      type string;
    }

	notification resetnotify {//error: unexpected keyword
      leaf reset-at {
        type string;
      }
    }

    action resetact {//error: unexpected keyword
      input {
        leaf start {
          type string;
        }
      }
      output {
        leaf finish {
          type string;
        }
      }
    }
  }
}
