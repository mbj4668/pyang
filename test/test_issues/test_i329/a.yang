module a {
  yang-version 1.1;
  namespace "urn:a";
  prefix test;
  container a {
    leaf ix {
      type int16;
      default 0x1234;
    }
    leaf io {
      type int16;
      default 01234;
    }
  }
}
