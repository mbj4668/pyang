module base {
  yang-version 1.1;
  namespace "urn:base";
  prefix b;

  grouping servers-grp {
    leaf-list servers {
      type string;
    }
  }

  container cfg {
    uses servers-grp;
  }

  leaf-list dns {
    type string;
    default "8.8.8.8";
  }
}
