module b {
  yang-version 1.1;
  namespace urn:b;
  prefix b;

  typedef value_restricted {
    type string {
      length 5..10;
      }
  }

  typedef typedef_value_restricted {
    type value_restricted {
      length "min | max";
    }
  }

  typedef error_value {
    type value_restricted {
      length "min .. min | max";
    }
  }

  typedef invalid_value {
    type value_restricted {
      length "min .. 3 | max";
    }
  }

  leaf le1 {
    type typedef_value_restricted;
    default "aaaaa";
  }
}
