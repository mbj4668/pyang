module a {
  yang-version 1.1;
  namespace urn:a;
  prefix a;

  typedef value_restricted {
    type int8 {
      range 5..10;
      }
  }

  typedef typedef_value_restricted {
    type value_restricted {
      range "min | max";
    }
  }

  typedef error_value {
    type value_restricted {
      range "min .. min | max";
    }
  }

  typedef invalid_value {
    type value_restricted {
      range "min .. 3 | max";
    }
  }

  leaf le1 {
    type typedef_value_restricted;
    default 10;
  }
}
