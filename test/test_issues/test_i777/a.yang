module a {
  namespace "urn:a";
  prefix a;

  list gizmos {
    key "gizmo-name";

    leaf gizmo-name {
      type string;
    }

    container gizmo-attrs {
      // to be augmented by other modules
    }
  }
}
