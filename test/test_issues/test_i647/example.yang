module example {
  yang-version 1.1;
  namespace "http://example.com/attrerror";
  prefix ex;
  
  identity my-base-identity;
  
  typedef identityref-type {
    type identityref {
      base my-base-identity;
    }
  }

  leaf some-leaf {
    type union {
      type uint16;
      type identityref-type;
      type enumeration {
        enum "enum--value";
      }
    }
    default "enum-value";
  }
}
