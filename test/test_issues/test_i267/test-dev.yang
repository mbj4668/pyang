module test-dev {
  yang-version 1.1;
  namespace urn:test-dev;
  prefix test-dev;
  import test {
    prefix t;
  }
  deviation /t:root/t:child/t:foo {
    deviate delete {
        mandatory true;
    }
    deviate add {
        config false;
    }
  }
  deviation /t:root/t:ll {
    deviate add {
      default "aaa"; // test case for #615
    }
  }
}
