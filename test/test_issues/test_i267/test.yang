module test {
  yang-version 1.1;

  namespace urn:test;

  prefix test;

  container root {
    list child {
      key name;
      leaf name {
        type string;
      }
      leaf foo {
        mandatory true;
        type string;
      }
    }

    leaf-list ll {
      type string;
    }
  }
}
