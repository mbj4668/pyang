module main {
  //yang-version "1.1";
  namespace "http://test.test";
  prefix test;

  include submain;

  revision 2018-06-27;

  container native {
    container ip {
      container vrf {
        leaf name {
          type string;
        }
      }
    }

    uses config-interface-grouping;
  }
}
