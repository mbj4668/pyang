module augmain {
  namespace "http://test.augmain";
  prefix aug;

  import main {
    prefix test;
  }

  //yang-version "1.1";
  revision 2021-07-12;

    container protocol {
       container bgp {
         leaf interface {
           type leafref {
             path "/test:native/test:ip-vrf/test:ip/test:vrf/test:forwarding-prefixed";
           }
         }
       }
    }
}
