module a {
  namespace urn:a;
  prefix a;

  import b {
    prefix b;
  }

  revision 2014-03-01;

  typedef my-union1 {
    type union {
      type int32 {
        range "1..23";
      }
      type string;
    }
  }

  typedef my-union2 {
    type union {
      type uint32;
      type string;
    }
  }

  typedef my-union3 {
     type union {
       type uint32;
       type string;
     }
     default "dummy";
  }

  leaf gegga {
    type leafref {
      path "/b:b/b:q";
    }
  }

  feature foo;

  identity x {
    base b:b;
  }

  grouping gg {
    leaf gggg {
      type string;
    }
  }


  typedef goo1 {
    type int32;
    default 42;
  }

  typedef goo2 {
    type goo1;
  }

  extension a {
    argument foo {
//      yin-element false;
    }
  }

  container x {
    presence foo;
    leaf bar {
      mandatory true;
      if-feature foo;
      type string;
      must "../arne/foo and ../baz";
    }
    uses gg {
      if-feature foo;
    }
    leaf-list baz {
      when "../bar = 'bar'";
      type string;
      max-elements 2;
    }
    list arne {
      key "foo bar";
      unique "x1 x2";
      leaf foo {
        type string;
      }
      leaf bar {
        type string;
      }
      leaf x1 {
        type string;
      }
      leaf x2 {
        type string;
      }
      leaf x3 {
        type string;
      }
    }
    leaf aaa {
      type goo2;
    }
    choice y {
      leaf yy {
        type identityref {
          base xx;
        }
      }
    }
    leaf a_union {
        type my-union1;
    }
    leaf b_union {
        type my-union3;
    }
  }

  identity xx;

  rpc foo {
    if-feature foo;
  }

  leaf bbb {
    type uint16;
  }

  leaf-list baz2 {
    type string;
  }

  leaf-list baz3 {
    type string;
    ordered-by user;
    min-elements 1;
    max-elements 5;
  }

  leaf-list baz4 {
    type int32;
    ordered-by system;
  }

  leaf-list baz5 {
    type int32;
  }

  leaf-list baz6 {
    type int32;
    ordered-by system;
  }

  leaf-list baz7 {
    type int32;
  }

}
