module j {
  yang-version 1.1;
  namespace urn:j;
  prefix j;

  revision 2014-04-01;

  leaf foo {
    type enumeration {
      enum f {
        value 2;
      }
    }
    when "../bar = 'bar'";
  }
  leaf bar {
    type string;
    when "../foo != 'f'";
  }
}
