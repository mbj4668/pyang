module f {
  namespace "urn:f";
  prefix f;

  identity b;
  identity b2;

  container b {
    leaf q {
      type string;
    }
    leaf q3 {
      type string;
    }
  }
  container c {
    leaf q {
      type string;
    }
  }
}
