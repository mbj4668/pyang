module a {
  yang-version 1.1;
  namespace urn:a;
  prefix a;

  import b {
    prefix b2;
  }
  revision 2014-04-01;

  typedef my-union1 {
    type union {
      type int32 {
        range "min..24";
      }
      type string;
    }
  }

  leaf gegga {
    type leafref {
      path "/b2:b/b2:q3";
    }
  }
  typedef my-union2 {
    type union {
      type int32 {
        range "min..24";
      }
      type string;
    }
  }

  typedef my-union3 {
     type union {
       type uint32;
       type string;
     }
     default "dummy";
  }

  feature foo {
    status obsolete;
  }

  typedef goo1 {
    type int32;
    default 42;
  }

  typedef goo2 {
    type goo1;
  }

  identity x {
    base b2:b;
  }
  grouping gg {
    status deprecated;
    leaf gggg {
      type string;
    }
    leaf-list baz {
      type string;
      units fo;
    }
    leaf ggg {
      type string;
    }
  }

  container x {
    presence foo;
    container qqqq {
      leaf qqqq {
        type string;
        mandatory true;
      }
    }
    leaf bar {
      mandatory true;
      type string;
      must "../arne/foo and ../baz";
    }
    uses gg {
      status obsolete;
      if-feature foo;
    }
    list arne {
      key "foo a:bar";
      unique "x1 a:x2 x3";
      leaf foo {
        type string;
      }
      leaf bar {
        type string;
      }
      leaf x1 {
        type string;
      }
      leaf x2 {
        type string;
      }
      leaf x3 {
        type string;
      }
    }
    leaf aaa {
      type goo2;
      default 42;
    }
    choice y {
      case yy {
        leaf yy {
          type identityref {
            base xx;
            base yy;
          }
        }
      }
      case zz {
        leaf zz {
          type string;
        }
      }
    }
    leaf a_union {
        type my-union1;
        default "my-default-1";
    }
    leaf b_union {
        type my-union3;
        default "my-default-2";
    }
  }

  identity xx;
  identity yy {
    base xx;
    base x;
  }


  rpc foo {
    input {
      leaf foo {
        type string;
      }
    }
  }

  extension a {
    argument foo {
      yin-element false;
    }
  }

  leaf bbb {
    type uint16 {
      range "5..5000 | 5500..6000";
    }
  }

  leaf-list baz2 {
    type string;
    min-elements 1;
    max-elements 4;
  }

  leaf-list baz3 {
    type string;
    ordered-by system;
    min-elements 2;
    max-elements 4;
  }

  leaf-list baz4 {
    type int32;
  }

  leaf-list baz5 {
    type int32;
    ordered-by system;
  }

  leaf-list baz6 {
    type int32;
    ordered-by user;
  }

  leaf-list baz7 {
    type int32;
    ordered-by user;
  }

}
