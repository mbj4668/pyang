submodule i_sub {
  belongs-to i {
     prefix i;
  }

  revision 2014-04-01;

  identity my_identity_1;

  extension my_ext_1;

  feature my_new_feature_1;

  typedef new_type_1 {
     type boolean;
  }
 
  grouping i-grouping-2 {
     container two {
        leaf l1 {
           type empty;
        }
        leaf l2 {
           type empty;
        }
     }
  }

  container b {
  }
}
