module ieee802-dot1q-psfp {
  namespace urn:ieee:std:802.1Q:yang:ieee802-dot1q-psfp;
  prefix psfp;

  import ieee802-dot1q-types {
    prefix dot1q-types;
  }

  import ieee802-dot1q-bridge {
    prefix dot1q;
  }

  import ieee802-dot1q-stream-filters-gates {
    prefix sfsg;
  }

  organization
    "IEEE 802.1 Working Group";

  description
    "This module provides management of 802.1Q bridge components that
    support Per Stream Filtering and Policing (PSFP).";

  revision 2020-07-07 {
    description
      "Published as part of IEEE Std 802.1Qcw.
      Initial version.";
    reference
      "IEEE Std 802.1Qcw - Bridges and Bridged Networks — Amendment:
      YANG Data Models for Scheduled Traffic, Frame Preemption, and
      Per-Stream Filtering and Policing.";
  }

  feature psfp {
    description
      "Per Stream Filtering and Policing supported.";
    reference
      "IEEE Std 802.1Q-2018";
  }

  grouping stream-gate-control-entries {
    description
      "A GateControlEntry consists of an operation name, followed by
      four parameters associated with the operation. The first
      parameter is a gateStatesValue; the second parameter is an IPV
      value; the third parameter is a timeIntervalValue; and the
      fourth parameter is an IntervalOctetMaxValue.
      IntervalOctetMaxValue is optional.";
    uses dot1q-types:base-gate-control-entries {
      refine "gate-control-entry/operation-name" {
        must ". = 'set-gate-and-ipv'";
      }
      augment "gate-control-entry" {
        description
          "Augment gate-control-entry from base-gate-control-entries
          with parameters gate-states-value, ipv-spec and
          interval-octet-max.";
        leaf gate-state-value {
          type sfsg:gate-state-value-type;
          mandatory true;
          description
            "The PSFPgateStatesValue indicates the desired gate state,
            open or closed, for the stream gate.";
          reference
            "12.31.3.2.1 of IEEE Std 802.1Q-2018";
        }
        leaf ipv-spec {
          type sfsg:ipv-spec-type;
          mandatory true;
          description
            "The IPV value indicates the IPV to be associated with
            frames that pass the gate.";
          reference
            "12.31.3.2.3 of IEEE Std 802.1Q-2018";
        }
        leaf interval-octet-max {
          type uint32;
          description
            "An unsigned integer, denoting a IntervalOctetMax in MSDU
            octets";
          reference
            "12.31.3.2.5 of IEEE Std 802.1Qcw";
        }
      }
    }
  }

  augment
    "/dot1q:bridges"+
    "/dot1q:bridge"+
    "/dot1q:component"+
    "/sfsg:stream-gates"+
    "/sfsg:stream-gate-instance-table" {
    description
      "Augment the Bridge component Stream Gate instances by
       a) operational gate states
       b) operational IPV values
       c) PTP controlled open and close transitions
       d) Management for PTP controlled open and close transitions";
    leaf oper-gate-states {
      type sfsg:gate-state-value-type;
      config false;
      description
        "The current state of the gate. PSFPOperGateStates is set by
        the List Execute state machine, and its initial value is
        determined by the value of the PSFPAdminGateStates variable.";
      reference
        "12.31.3.2.1 of IEEE Std 802.1Q-2018
        8.6.10.5 of IEEE Std 802.1Q-2018";
    }
    leaf oper-ipv {
      type sfsg:ipv-spec-type;
      description
        "The operational internal priority value specification.";
      reference
        "12.31.3.3 of IEEE Std 802.1Q-2018
        8.6.10.7 of IEEE Std 802.1Q-2018
        8.6.5.1.2 of IEEE Std 802.1Q-2018";
    }
    container admin-control-list {
      config true;
      description
        "The AdminControlList and OperControlList are ordered
        lists containing AdminControlListLength or OperControlListLength
        entries, respectively. Each entry represents a gate operation.
        Each entry in the list is structured as a GateControlEntry.";
      reference
        "12.31.3.2 of IEEE Std 802.1Q-2018
        12.31.3.2.2 of IEEE Std 802.1Q-2018
        8.6.9.4.2 of IEEE Std 802.1Q-2018";
      uses stream-gate-control-entries;
    }
    container oper-control-list {
      config false;
      description
        "The AdminControlList and OperControlList are ordered
        lists containing AdminControlListLength or OperControlListLength
        entries, respectively. Each entry represents a gate operation.
        Each entry in the list is structured as a GateControlEntry.";
      reference
        "12.31.3.2 of IEEE Std 802.1Q-2018
        12.31.3.2.2 of IEEE Std 802.1Q-2018
        8.6.9.4.19 of IEEE Std 802.1Q-2018";
      uses stream-gate-control-entries;
    }

    container admin-cycle-time {
      description
        "The administrative value of the gating cycle for the Port.
        This value can be changed by management, and is used by the
        List Config state machine to set the value of OperCycleTime.
        The AdminCycleTime variable is a rational number of seconds,
        defined by an integer numerator and an integer denominator.";
      reference
        "12.29.1.3 of IEEE Std 802.1Q-2018
        8.6.9.4.3 of IEEE Std 802.1Q-2018";
      uses dot1q-types:rational-grouping;
    }
    container oper-cycle-time {
      config false;
      description
        "The operational value of the gating cycle for the Port. This
        variable is set dynamically from the AdminCycleTime variable
        under the control of the List Config state machine
        OperCycleTime is used by the Cycle Timer state machine to
        enforce the cycle time for the Port. The OperCycleTime
        variable is a rational number of seconds, defined by an
        integer numerator and an integer denominator.";
      reference
        "12.29.1.3 of IEEE Std 802.1Q-2018
        8.6.9.4.20 of IEEE Std 802.1Q-2018";
      uses dot1q-types:rational-grouping;
    }
    leaf admin-cycle-time-extension {
      type uint32;
      units "nanoseconds";
      description
        "An integer number of nanoseconds, defining the maximum amount
        of time by which the gating cycle for the Port is permitted to
        be extended when a new cycle configuration is being installed.
        This administrative value can be changed by management, and is
        used by the List Config state machine to set the value of
        OperCycleTimeExtension.";
      reference
        "8.6.9.4.4 of IEEE Std 802.1Q-2018";
    }
    leaf oper-cycle-time-extension {
      type uint32;
      units "nanoseconds";
      config false;
      description
        "An integer number of nanoseconds, defining the maximum amount
        of time by which the gating cycle for the Port is permitted to
        be extended when a new cycle configuration is installed. This
        operational value is set by the List Config state machine to
        the value of AdminCycleTimeExtension. The value of
        OperCycleTimeExtension is used by the SetCycleStartTime()
        procedure.";
      reference
        "8.6.9.4.21 of IEEE Std 802.1Q-2018";
    }
    container admin-base-time {
      description
        "The administrative value of base time, expressed as an IEEE
        1588 precision time protocol (PTP) timescale (see IEEE Std
        802.1AS-2011). This value can be changed by management, and is
        used by the List Config state machine to set the value of
        OperBaseTime.";
      reference
        "12.29.1.4 of IEEE Std 802.1Q-2018
        8.6.9.4.1 of IEEE Std 802.1Q-2018";
      uses dot1q-types:ptp-time-grouping;
    }
    container oper-base-time {
      config false;
      description
        "The operational value of base time, expressed as a PTP
        timescale (see IEEE Std 802.1AS-2011). This variable is used
        by the List Config state machine.";
      reference
        "12.29.1.4 of IEEE Std 802.1Q-2018
        8.6.9.4.18 of IEEE Std 802.1Q-2018";
      uses dot1q-types:ptp-time-grouping;
    }
    leaf config-change {
      type boolean;
      description
        "A Boolean variable that acts as a start signal to the List
        Config state machine that the administrative variable values
        for the Port are ready to be copied into their corresponding
        operational variables. This variable is set TRUE by management
        and is set FALSE by the List Config state machine.";
      reference
        "8.6.9.4.7 of IEEE Std 802.1Q-2018";
    }
    container config-change-time {
      config false;
      description
        "The time at which the administrative variables that determine
        the cycle are to be copied across to the corresponding
        operational variables, expressed as a PTP timescale. The value
        of this variable is set by the SetConfigChangeTime() procedure
        in the List Config state machine.";
      reference
        "12.29.1.4 of IEEE Std 802.1Q-2018
        8.6.9.4.9 of IEEE Std 802.1Q-2018";
      uses dot1q-types:ptp-time-grouping;
    }
    leaf tick-granularity {
      type uint32;
      config false;
      description
        "Characteristics of an implementation’s cycle timer clock
        (TickGranularity).";
      reference
        "8.6.9.4.16 of IEEE Std 802.1Q-2018";
    }
    container current-time {
      config false;
      description
        "The current time maintained by the local system, expressed as
        a PTP timescale (see IEEE Std 802.1AS-2011).";
      reference
        "12.29.1.4 of IEEE Std 802.1Q-2018
        8.6.9.4.10 of IEEE Std 802.1Q-2018";
      uses dot1q-types:ptp-time-grouping;
    }
    leaf config-pending {
      type boolean;
      config false;
      description
        "A Boolean variable, set TRUE by the List Config state machine
        to signal that there is a new cycle configuration awaiting
        installation. The variable is set FALSE when the List Config
        state machine has installed the new configuration. The
        variable is used by the SetCycleStartTime() procedure to
        control the length of the cycle that immediately precedes the
        first cycle that uses the new configuration values. This value
        can be read by management.";
      reference
        "8.6.9.3 of IEEE Std 802.1Q-2018
        8.6.9.4.8 of IEEE Std 802.1Q-2018";
    }
    leaf config-change-error {
      type uint64;
      config false;
      description
        "An error counter that is incremented if AdminBaseTime
        specifies a time in the past, and the current schedule is
        running.";
      reference
        "8.6.9.3.1 of IEEE Std 802.1Q-2018";
    }
    leaf gate-closed-due-to-invalid-rx-enable {
      type boolean;
      default "false";
      description
        "A value of TRUE indicates that the GateClosedDueToInvalidRx
        function is enabled; a value of FALSE indicates that the
        GateClosedDueToInvalidRx function is disabled. The default
        value of GateClosedDueToInvalidRxEnable is FALSE.";
      reference
        "8.6.5.1.2 of IEEE Std 802.1Q-2018";
    }
    leaf gate-closed-due-to-invalid-rx {
      type boolean;
      default "false";
      description
        "If GateClosedDueToInvalidRxEnable is TRUE, a value of TRUE in
        GateClosedDueToInvalidRx indicates that all frames are dropped
        (i.e., the gate behaves as if the operational stream gate
        state is Closed). If GateClosedDueToInvalidRx is FALSE, it has
        no effect. The default value of GateClosedDueToInvalidRx is
        FALSE; if any frame is discarded because the gate is in the
        Closed state, then GateClosedDueToInvalidRx is set TRUE.";
      reference
        "8.6.5.1.2 of IEEE Std 802.1Q-2018";
    }
    leaf gate-closed-due-octets-exceeded-enable {
      type boolean;
      default "false";
      description
        "A value of TRUE indicates that the
        GateClosedDueToOctetsExceeded function is enabled; a value of
        FALSE indicates that the GateClosedDueToOctetsExceeded
        function is disabled. The default value of
        GateClosedDueToOctetsExceed is FALSE.";
      reference
        "8.6.5.1.2 of IEEE Std 802.1Q-2018";
    }
    leaf gate-closed-due-octets-exceeded {
      type boolean;
      default "false";
      description
        "If GateClosedDueToOctetsExceededEnable is TRUE, a value of
        TRUE in GateClosedDueToOctetsExceeded indicates that all
        frames are dropped (i.e., the gate behaves as if the
        operational stream gate state is Closed). If
        GateClosedDueToOctetsExceeded is FALSE, it has no effect. The
        default value of GateClosedDueToOctetsExceeded is FALSE; if
        any frame is discarded because there are insufficient
        IntervalOctetsLeft, then GateClosedDueToOctetsExceeded is set
        TRUE.";
      reference
        "8.6.5.1.2 of IEEE Std 802.1Q-2018";
    }
  }
}
