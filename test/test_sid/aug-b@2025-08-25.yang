module aug-b {
  yang-version 1.1;
  namespace "urn:example:aug_b";
  prefix ab;

  import aug-a {
    prefix aa;
  }

  revision 2025-08-25;

  augment "/aa:top-level/aa:b" {
    leaf b {
      type int16;
    }
  }

  augment "/aa:top-level" {
    case c {
      leaf c {
        type int32;
      }
    }

    case d { }
  }
}
