module r {
  namespace urn:r;
  prefix r;

  import ietf-restconf {
    prefix rc;
  }

  rc:yang-data foo {
    choice c {
      container x;
      case a {
        container y;
      }
      case b {
        choice q {
          case z {
            leaf foo {
              type string;
            }
          }
        }
      }
    }
  }
  rc:yang-data bar {
    choice c {
      container x;
      case a {
        container y;
        container z;
      }
      case b {
        choice q {
          case z {
            container p;
          }
        }
      }
    }
  }

}
