module list2 {
  yang-version 1.1;
  namespace "urn:test:list2";
  prefix "l";

  choice test {
    default node;
    case node {
      leaf  mandatory {
        type string;
        mandatory true; // error: no mandatory under default case
      }
      list mandatory2 { // error: no mandatory under default case
        min-elements "3";
        key "name";
        leaf name {
          type string;
        }
      }
      anyxml aa { // error: no mandatory under default case
        mandatory true;
      }
      anydata bb { // error: no mandatory under default case
        mandatory true;
      }
      container x {
        anyxml cc { // error: no mandatory under default case
          mandatory true;
        }
        anydata dd { // error: no mandatory under default case
          mandatory true;
        }
        container y {
          leaf-list m {
            min-elements "1"; // error: no mandatory under default case
            type string;
          }
        }
      }
    }
  }
  
}
