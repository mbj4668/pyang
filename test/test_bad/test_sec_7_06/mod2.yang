module mod2 {
  yang-version 1.1;
  namespace "urn:mod2";
  prefix m2;

  grouping gg2 {
    leaf le2 {
      type string;
    }
  }  

  leaf le3 {
    type string;
    description "test description";
    reference " test reference";
    config true;
    status "current";
    units "pk";
    when "../le4 = 255";
    default "hello";
    mandatory false;

    description "test description1"; // error: duplicate description
    reference " test reference1"; // error: duplicate reference
    config true1; // error: duplicate config
    status "current1"; // error: duplicate status
    units "pk1"; // error: duplicate units
    when "../le4 = 256"; // error: duplicate when
    default "hello1"; // error: duplicate default
    mandatory false; // error: duplicate mandatory

  }

  leaf le4 {
    type uint16;
  }
  

}
