module mod2 {
  yang-version 1.1;
  namespace "urn:mod2";
  prefix m2;

  yang-version 1.1; // too many yang-version
  namespace "urn:aa"; // too many namespace
  prefix mm; // too many prefix

  grouping gg2 {
    leaf le2 {
      type string;
    }
  }
}
