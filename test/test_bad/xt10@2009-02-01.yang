module xt1x { // error: does not match filename
  namespace "urn:xt10";
  prefix "xt10";

  revision 2009-02-01 {
    description "second update";
  }

  revision 2009-01-01 {
    description "first update";
  }

  typedef a {
    type string;
  }

/*
  typedef b {
    type string;
  }
*/

  typedef c {
    type string;
  }

}
