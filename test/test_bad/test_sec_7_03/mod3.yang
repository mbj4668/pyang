module mod3 {
  yang-version 1.1;
  namespace "urn:mod3";
  prefix m3;

  typedef my_base3 {
    type string {
      pattern '[a-z]+';
    }
    default 'xqwe';
  }

  container con3 {
    leaf le3 {
      type my_base3 {
        length "1..3"; // error: the default value "xqwe" does not match its base type
      }
    }
  }

  typedef value1 {
    type int16 {
      range "1..100 | 128..512";
    }
    default "256";
  }

  typedef value2 {
    type value1 {
      range "192 .. 255"; // error: bad value "256"
    }
  }

  leaf lee {
    type value1; 
  }

}
