module u {
  yang-version 1.1;
  namespace "urn:u";
  prefix u;

  feature foo;

  feature bar;

  container a {
    if-feature "foo and not bar";
  }
  container t {
    notification x;
    action reset {
      input {
        leaf time {
          type string;
        }
      }
    }
  }
}
