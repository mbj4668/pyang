module yt6 {

    namespace "urn:ietf:params:xml:ns:yang:yt6";
    prefix "yt6";

    import ietf-yang-types { prefix y; }

    organization
        "YANG Language Design Team";

    contact
        "Andy Bierman";

    description
        "YANG test module 6. Container, augment";


  typedef un-1 {
    type union {   // 16
      type union {  // 17
        type int32;
        type binary;
        type union {  // 20
          type string;
          type binary;
          type boolean;
        }
      }
      type int64;
    }
    default 9;
  }

  augment /foo/a/z {
     leaf xxx { type binary; }
  }

  augment /foo/a {
     case zz { leaf zzz { type int64; } }
  }


  container foo {
     leaf un { 
       type un-1;
       config false; 
       default forty;
     }
     leaf bar1 { 
        type y:counter32; 
     }
     leaf bar2 { 
        type int32; 
        default 10;
     }
     leaf bar3 { 
        type int32; 
        mandatory true;
     }
     leaf bar4 { 
        type int32; 
        mandatory false;
     }
     leaf bar5 { 
        type int32; 
        mandatory true;
        // default 10;  pyang says this is illegal
     }
     leaf bar6 { 
        type int32; 
        mandatory false;
        default 10;
     }
     choice a {
       default x;
       leaf x { type int32; }
       leaf y { type string; }
       container z;
     } 
  }

  list bar {
    config false;
    key bar1;
    unique zz2;
    leaf zz1 { type un-1; mandatory true; }
    leaf zz2 { type y:zero-based-counter32; }
    leaf-list zz3 {
      description testing-one-two-three;
      min-elements 4;
      max-elements 14;
      type y:date-and-time;
      ordered-by user;
    }
    leaf bar1 { type un-1; }
  }

  notification notif1 {
    description "notification test";
    reference test-notif-1;
    status deprecated;
    container x {
      list y {
        reference "RFC 4741";
        leaf xx { type int32; }
        leaf zz { type zz_type; }

        key xx;

        max-elements "77";
        min-elements "15";
      }

      leaf yy { type int32; default -123; }

      typedef zz_type {
        type enumeration {
          enum x;
          enum y;
        }
      }
    }
    leaf x2 { type instance-identifier; }
    anyxml x3 { description test-any; }
  }

  notification notif2;

}
