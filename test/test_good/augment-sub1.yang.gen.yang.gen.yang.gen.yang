submodule augment-sub1 {
  belongs-to augment-super {
    prefix as;
  }

  include augment-sub0;

  augment "/interfaces" {
    list ifEntry {
      key "ifIndex";
      leaf ifIndex {
        type int32;
      }
    }
    leaf llm1 {
      type string;
      mandatory true;
    }
  }
}
