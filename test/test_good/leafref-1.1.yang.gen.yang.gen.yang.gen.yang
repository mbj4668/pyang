module leafref-1.1 {
  yang-version 1.1;
  namespace "urn:example:ll";
  prefix ll;

  container x {
    leaf foo {
      type string;
    }
    leaf bar {
      type leafref {
        path "../foo";
        require-instance false;
      }
    }
    list q {
      key "a";
      leaf a {
        type string;
      }
      leaf b {
        type string;
      }
    }
  }

  grouping x {
    leaf a {
      type string;
    }
    leaf b {
      type leafref {
        path "/ll:x/ll:q[ll:a = current()/../a]/ll:b";
      }
    }
  }
}
