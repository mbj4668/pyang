module example-module-aug {
    yang-version 1.1;
    namespace "urn:example:example-module-aug";
    prefix exma;

    import ietf-yang-structure-ext {
      prefix sx;
      revision-date 2020-06-17;
    }
    import example-module {
      prefix exm;
      revision-date 2020-06-17;
    }

    sx:augment-structure "/exm:address-book/exm:address" {
      leaf county {
        type string;
        description "County name";
      }
      leaf zipcode {
        type string;
        description "Postal zipcode";
      }
    }
 }
