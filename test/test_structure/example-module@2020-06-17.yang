module example-module {
  yang-version 1.1;
  namespace "urn:example:example-module";
  prefix em;

  import ietf-yang-structure-ext {
    prefix sx;
    revision-date 2020-06-17;
  }

  revision 2020-06-17;

  sx:structure address-book {
    list address {
      key "last first";
      leaf last {
        type string;
        description "Last name";
      }
      leaf first {
        type string;
        description "First name";
      }
      leaf street {
       type string;
        description "Street name";
      }
      leaf city {
        type string;
        description "City name";
      }
      leaf state {
        type string;
        description "State name";
      }
    }
  }
}
