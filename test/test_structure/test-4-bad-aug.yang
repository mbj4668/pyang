module test-4-bad-aug {
  yang-version 1.1;
  namespace "urn:example:test-4";
  prefix t;

  import ietf-yang-structure-ext {
    prefix sx;
    revision-date 2020-06-17;
  }

  container not_struct {
    container inner {
      leaf l {
        type int32;
      }
    }
  }

  sx:augment-structure "/not_struct/inner" {
    leaf l2 {
      type string;
    }
  }
}
