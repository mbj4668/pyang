module union-test-bed {
  yang-version 1.1;
  namespace "http://union-test-bed";
  prefix utb;

  description
    "This is a made up yang file for pyang testing of union subtypes";


  /*
   * Typedefs
   */

  typedef leafref-to-union-type {
    type leafref {
      path "/utb:base-type-unions/basic-union";
    }
  }
  
  typedef enumeration-type {
	  type enumeration {
		  enum 'a';
		  enum 'b';
	  }
  }

  typedef union-type {
	  type union {
		  type string;
		  type uint32;
		  type enumeration-type;
	  }
  }
  
  container base-type-unions {
	  
	  leaf single-value {
		  type uint16;
	  }
	  
	  leaf basic-union {
		  type union {
			  type int16;
			  type string;
		  }
	  }
	  
	  leaf union-leafref {
		  type union {
			  type string;
			  type leafref {
				path "/utb:base-types/single-value";			  
			  }
		  }
	  }
	  
	  leaf union-of-union {
		  type union {
			  type string;
			  type union {
				  type uint16;
				  type boolean;
			  }
		  }
	  }
	  
	  leaf union-of-enumeration {
		  type union {
			  type enumeration {
				  enum 'enum1';
				  enum 'enum2';
			  }
			  type int32;
		  }
	  }
	  
  }
  
  container with-typedefs {
	  leaf leafref-to-union {
		  type leafref-to-union-type;
	  }
	  
	  leaf union-with-enumeration {
		  type union {
			  type string;
			  type enumeration-type;
		  }
	  }
	  
	  leaf union-through-typedef {
		  type union-type;
	  }
  }

}
