submodule xt1s1 {
  belongs-to xt1 {prefix xt1; }
  import xt3 { prefix xt3p; } // different prefix than in xt1
  organization "hopp";
  contact "hej" {
    xt3p:test hej {}
    xt3:test hej {xt3:hemm he;} // error: bad prefix
  }
  revision 2007-06-06 { description "initinla"; }

    container sub1 {
        leaf q {
            type int32;
        }
    }

}
