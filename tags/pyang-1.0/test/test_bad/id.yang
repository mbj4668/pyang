module id {
  namespace "urn:id";
  prefix id;

  import "crypto-base" {
    prefix "crypto";
  }

  feature x { // error: circular
    if-feature y;
  }

  feature y {
    if-feature x;
  }

  feature z {
    if-feature x2; // error: x2 does not exist
  }

  feature z; // error: already defined

  leaf foo {
    if-feature x;
    type string;
  }

  leaf foo2 {
    if-feature x2; // error: not defined
    type string;
  }

  identity x { // error: circular
    base y;
  }

  identity y {
    base x;
  }

  identity y; // error: already defined

  identity des {
    base "crypto:crypto-alg";
    description "DES crypto algorithm";
  }
  
  identity des3 {
    base "crypto:crypto-alg";
    description "Triple DES crypto algorithm";
  }
  
  identity des4 {
    base "crypto:crypto-alg2"; // error: not defined
    description "Triple DES crypto algorithm";
  }
  
  identity des5 {
    base "crypto-alg2"; // error: not defined
    description "Triple DES crypto algorithm";
    base "crypto-alg2"; // error: syntax
  }

  typedef crypto-type {
    type identityref {
      base "crypto:crypto-alg";
    }
  }

  typedef crypto-type1 {
    type identityref {
      base "crypto:crypto-alg2"; // error: not defined
    }
  }

  typedef crypto-type2 {
    type identityref {
      base "crypto-alg2"; // error: not defined
    }
  }

  typedef crypto-type3 {
    type int32 {
      base "crypto:crypto-alg"; // error: bad restriction
    }
  }

  typedef crypto-type4 {
    type identityref {
      pattern "a*"; // error; bad restriction
    }
  }

  identity z;

  leaf x1 {
    type identityref {
      base crypto:crypto-alg;
    }
    default z; // error; z not derived from crypto-alg
  }

  leaf x2 {
    type identityref {
      base crypto:crypto-alg;
    }
    default crypto:crypto-alg;
  }

  leaf x3 {
    type identityref {
      base crypto:crypto-alg;
    }
    default des3;
  }

  leaf x4 {
    type identityref {
      base crypto:crypto-alg;
    }
    default id:des3;
  }

}
