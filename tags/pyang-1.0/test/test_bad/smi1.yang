module smi1 {

  smi:oid "1.3.6.4.1";

  namespace urn:t;
  prefix a;

  import yang-smi {
    prefix smi;
  }

  leaf x {
    type int32;
    smi:oid "1.3.6.4.1";
  }

  leaf y {
    type int32;
    smi:oid "foobar"; // error: not an OID 
  }

  typedef foo {
    type int32;
    smi:oid "1.3.3.4"; // error: oid not allowed here
                       // this tests that extension grammar works
  }
}
